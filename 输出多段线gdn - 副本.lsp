(vl-load-com)
;;;输出节点数据
(defun C:gdn()
  (princ "\n输出节点数据\n")
  (setq fp (open "输出节点数据.txt" "w"))
  (setq ss (ssget "X" '((0 . "LWPOLYLINE"))))
  (setq ss (ssget '((0 . "LWPOLYLINE"))))
  (if (= ss nil) (exit))
  (setq en (car (entsel "选择多线段")))
  (if (= en nil) (exit)) 
  (setq pl (vlax-ename->vla-object en))
  (setq tab nil) 
  (setq n0 (sslength ss))
  (setq i 0)
  
  (repeat n0
    (setq ent (ssname ss i))
    (setq txt (vlax-ename->vla-object ent))
    (setq coo (vla-get-coordinates txt))
    (setq var (vlax-variant-value coo))
    (setq pts (vlax-safearray->list var))
    (setq num (length pts))
    (setq tab (append tab (list (append (list (/ num 2)) pts))))
    (setq i (+ i 1))
    ) ;end repeat
  (setq n1 (length tab))
  (setq i 0)
  (repeat n1    
    (setq L (nth i tab))
    (setq num (length L))
    (setq x1 (nth 0 L)) 
    (setq str (strcat (rtos (1+ i) 2 0) "\t" (rtos x1 2 0) "\n"))
    (setq j 1)
    (repeat (/ (1- num) 2)
      (setq x1 (nth j L)) 
      (setq y1 (nth (1+ j) L)) 
      (setq str (strcat str (rtos x1 2 6) "\t" (rtos y1 2 6) "\n"))   
      (setq j (+ j 2))
    )
    (setq str (strcat str  "\n"))
    (princ str fp)
    (setq i (1+ i))
    ) ;end repeat
    
  (close fp)
  (print n1)
  (princ)
  )
